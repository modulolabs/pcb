/*
 *  This EAGLE User Language Program creates the proper format
 *  Centroid file for assembly at Screaming Circuits including
 *  the reference designator, position, layer and orientation
 *  of each part
 *
 *
 *  Version 1.0,  May 16, 2006
 *
 *  www.screamingcircuits.com
 *
 */


string rotation(real Angle)
{
  string s;

  sprintf(s, "%.1f", Angle);
  for (int i = 0; s[i]; i++)
      if (s[i] == '.') {
         if (s[i + 1] == '0')
            s[i] = 0;
         break;
         }
   return s;
}

string side(int Mirror)
{
  string s;

  if (Mirror){
     s = "Bottom";
     }
     else {
     s = "Top";
     }
  return s;
}

board(B) {
    output(argv[1]) {
        printf("%s,%s,%s,%s,%s\n", "RefDes", "Layer", "LocationX", "LocationY", "Rotation");
        B.elements(E) {
            int isSmd;
            isSmd = 0;
            E.package.contacts(C) {
                if (C.smd)
                    isSmd = 1;
            }
            if (isSmd)
               printf("%s,%s,%5.3f,%5.3f,%s\n", E.name, side(E.mirror), u2inch(E.x), u2inch(E.y), rotation(E.angle));
        }
    }
}
